module _3gpp-nr-nrm-externalenbfunction {
  yang-version 1.1;
  namespace "urn:3gpp:sa5:_3gpp-nr-nrm-externalenbfunction";
  prefix "extenb3gpp";

  import _3gpp-common-managed-function { prefix mf3gpp; }
  import _3gpp-nr-nrm-eutranetwork { prefix eutranet3gpp; }
  import _3gpp-common-subnetwork { prefix subnet3gpp; }
  import _3gpp-common-top { prefix top3gpp; }

  organization "3GPP SA5";
  description "Defines the YANG mapping of the ExternalENBFunction
    Information Object Class (IOC) that is part of the NR Network Resource
    Model (NRM).
    Copyright 2023, 3GPP Organizational Partners (ARIB, ATIS, CCSA, ETSI, TSDSI, 
    TTA, TTC). All rights reserved.";
  reference "3GPP TS 28.541 5G Network Resource Model (NRM),
    3GPP TS 28.658 (E-UTRAN) Network Resource Model (NRM)";

  revision 2023-09-18 { reference CR-1043 ; } 
  revision 2019-10-28 { reference S5-193518 ; }
  revision 2019-06-17 {
    description "Initial revision";
  }

  grouping ExternalENBFunctionGrp {
    description "Represets the ExternalENBFunction IOC.";
    reference "3GPP TS 28.658";
    uses mf3gpp:ManagedFunctionGrp;

    leaf eNBId {
      description "Unambiguously identifies an eNodeB within a PLMN.";
      reference "3GPP TS 36.413, 3GPP TS 36.300";
      mandatory true;
      type int32 { range "0..268435455"; } // Representing 28 bit eNB ID.
                                           // 18, 20 and 21 bit eNB IDs also
                                           // allowed.
    }
  }

  grouping ExternalENBFunctionWrapper {
    list ExternalENBFunction {
      description "Represents an external eNB functionality.";
      reference "3GPP TS 28.658";
      key id;
      uses top3gpp:Top_Grp;
      container attributes {
        uses ExternalENBFunctionGrp;
      }
      uses mf3gpp:ManagedFunctionContainedClasses;
    }
  } 
  
  augment "/subnet3gpp:SubNetwork" {
    if-feature subnet3gpp:ExternalsUnderSubNetwork ;
    uses ExternalENBFunctionWrapper;
  }

  augment "/eutranet3gpp:EUtraNetwork" {
    if-feature eutranet3gpp:ExternalsUnderEUtraNetwork;
    uses ExternalENBFunctionWrapper;
  }
}

module _3gpp-5gc-nrm-upffunction {
  yang-version 1.1;
  namespace urn:3gpp:sa5:_3gpp-5gc-nrm-upffunction;
  prefix upf3gpp;

  import _3gpp-common-managed-function { prefix mf3gpp; }
  import _3gpp-common-managed-element { prefix me3gpp; }
  import _3gpp-common-yang-types { prefix types3gpp; }
  import _3gpp-5g-common-yang-types { prefix types5g3gpp; }
  import _3gpp-common-top { prefix top3gpp; }

  organization "3GPP SA5";
  contact "https://www.3gpp.org/DynaReport/TSG-WG--S5--officials.htm?Itemid=464";
  description "UPFFunction derived from basic ManagedFunction.
    Copyright 2023, 3GPP Organizational Partners (ARIB, ATIS, CCSA, ETSI, TSDSI, 
    TTA, TTC). All rights reserved.";
  reference "3GPP TS 28.541 5G Network Resource Model (NRM)";

  revision 2023-09-18 { reference CR-1043 ; } 
  revision 2023-04-26 { reference CR-0916; }
  revision 2020-11-08 { reference CR-0412 ; }
  revision 2019-10-25 { reference "S5-194457 S5-193518"; }
  revision 2019-05-31 { reference "Ericsson refactoring."; }
  revision 2018-08-07 { reference "Initial revision"; }

  grouping UPFFunctionGrp {
    description "Represents the UPFFunction IOC";
    uses mf3gpp:ManagedFunctionGrp;

    list pLMNIdList {
      description "A list of PLMN identifiers (Mobile Country Code and Mobile 
        Network Code).";
      min-elements 1;
      key "mcc mnc";
      uses types3gpp:PLMNId;
    }

    leaf-list nRTACList {
      description "List of Tracking Area Codes (legacy TAC or extended TAC) 
                   where the represented management function is serving.";
                   reference "TS 38.413 clause 9.3.3.10";
      min-elements 1;
      config false;
      type types3gpp:Tac;
    }

    list sNSSAIList {
      description "List of S-NSSAIs the managed object is capable of supporting.
                   (Single Network Slice Selection Assistance Information)
                   An S-NSSAI has an SST (Slice/Service type) and an optional SD 
                  (Slice Differentiator) field.";
      reference "3GPP TS 23.003";
      key "sd sst";
      uses types5g3gpp:SNssai;
    }
    
    list managedNFProfile {
      key idx;
      min-elements 1;
      max-elements 1;
      description "Profile definition of a Managed NF (See TS 23.501)";
      uses types3gpp:ManagedNFProfile;
    }
 
    leaf-list supportedBMOList {
      type string;
      description "List of supported BMOs (Bridge Managed Objects) required 
        for integration with TSN system.";
    }
  }

  augment /me3gpp:ManagedElement {
    list UPFFunction {
      description "5G Core UPF Function";
      reference "3GPP TS 28.541";
      key id;
      uses top3gpp:Top_Grp;
      container attributes {
        uses UPFFunctionGrp;
      }
      uses mf3gpp:ManagedFunctionContainedClasses;
    }
  }
}

module _3gpp-nr-nrm-bwpset {
  yang-version 1.1;
  namespace "urn:3gpp:sa5:_3gpp-nr-nrm-bwpset";
  prefix "bwpset3gpp";

  import _3gpp-common-managed-element { prefix me3gpp; }
  import _3gpp-common-managed-function { prefix mf3gpp; }
  import _3gpp-common-top { prefix top3gpp; }
  import _3gpp-nr-nrm-gnbdufunction { prefix gnbdu3gpp; }

  organization "3GPP SA5";
  contact "https://www.3gpp.org/DynaReport/TSG-WG--S5--officials.htm?Itemid=464";
  description "Defines the YANG mapping of the BWPSet Information Object Class
    (IOC) that is part of the NR Network Resource Model (NRM).
    Copyright 2023, 3GPP Organizational Partners (ARIB, ATIS, CCSA, ETSI, TSDSI, 
    TTA, TTC). All rights reserved.";
  reference "3GPP TS 28.541 5G Network Resource Model (NRM)";

  revision 2023-09-18 { reference CR-1043 ; } 
  revision 2022-06-29 { reference CR-0756 ; }

  grouping BWPSetGrp {
    description "Represents the BWPSet IOC.";
    reference "3GPP TS 28.541";
    uses mf3gpp:ManagedFunctionGrp;
  }
  augment "/me3gpp:ManagedElement/gnbdu3gpp:GNBDUFunction" {

    list BWPList {
      description "Represents a bandwidth part (BWP) set.";
      key id;
      uses top3gpp:Top_Grp;
      container attributes {    
        uses BWPSetGrp;
      }
      uses mf3gpp:ManagedFunctionContainedClasses;
    }
  }
}

module _3gpp-nr-nrm-danrmanagementfunction {
  yang-version 1.1;
  namespace "urn:3gpp:sa5:_3gpp-nr-nrm-danrmanagementfunction";
  prefix "danrmanagementfunction3gpp";


  import _3gpp-common-top { prefix top3gpp; }
  import _3gpp-nr-nrm-gnbcucpfunction { prefix gnbcucp3gpp; }
  import _3gpp-common-managed-element { prefix me3gpp; }

 

  organization "3GPP SA5";
  contact "https://www.3gpp.org/DynaReport/TSG-WG--S5--officials.htm?Itemid=464";
  description "Defines the YANG mapping of the DANRManagementFunction Information Object Class
    (IOC) that is part of the NR Network Resource Model (NRM).
    Copyright 2023, 3GPP Organizational Partners (ARIB, ATIS, CCSA, ETSI, TSDSI, 
    TTA, TTC). All rights reserved.";
  reference "3GPP TS 28.541 5G Network Resource Model (NRM)";

  revision 2023-09-18 { reference CR-1043 ; } 
  revision 2020-05-08 { reference S5-203316; }


  grouping DANRManagementFunctionGrp {
    description "Represents the DANRManagementFunction IOC.";
    reference "3GPP TS 28.541";
    uses top3gpp:Top_Grp;

    leaf intrasystemANRManagementSwitch {
        description "This attribute determines whether the intra-system ANR function is activated or deactivated.";
         type boolean;
    }

    leaf intersystemANRManagementSwitch {
        description "This attribute determines whether the inter-system ANR function is activated or deactivated.";
        type boolean;
    }

    
  }

  augment "/me3gpp:ManagedElement/gnbcucp3gpp:GNBCUCPFunction" {
    if-feature gnbcucp3gpp:DANRManagementFunction;
    uses DANRManagementFunctionGrp;
  }
}

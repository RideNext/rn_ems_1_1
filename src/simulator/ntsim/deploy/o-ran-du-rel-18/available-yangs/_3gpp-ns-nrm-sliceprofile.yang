submodule _3gpp-ns-nrm-sliceprofile {
  yang-version 1.1;
  belongs-to _3gpp-ns-nrm-networkslicesubnet { prefix nss3gpp; }

  import _3gpp-common-yang-types { prefix types3gpp; }
  import _3gpp-5g-common-yang-types { prefix types5g3gpp; }
  // import _3gpp-ns-nrm-networkslice { prefix ns3gpp; }
  import _3gpp-ns-nrm-common { prefix ns3cmn3gpp; }
  
  organization "3GPP SA5";
  contact 
    "https://www.3gpp.org/DynaReport/TSG-WG--S5--officials.htm?Itemid=464";
  description "Represents the properties of network slice subnet related 
    requirement that should be supported by the network slice subnet 
    instance in a 5G network.
    Copyright 2023, 3GPP Organizational Partners (ARIB, ATIS, CCSA, ETSI, TSDSI, 
    TTA, TTC). All rights reserved.";
  reference "3GPP TS 28.541
    Management and orchestration; 
    5G Network Resource Model (NRM);
    Information model definitions for network slice NRM (chapter 6)
    ";

  revision 2023-11-04 { reference CR-1129; }
  revision 2023-09-18 { reference CR-1043 ; } 
  revision 2023-04-26 { reference CR-0916; }
  revision 2021-07-20 { reference CR-0566; } 
  revision 2021-05-05 { reference CR-0485; }

  revision 2020-02-19 {
    description "Introduction of YANG definitions for network slice NRM";
    reference "CR-0458";
  }
  
  revision 2019-05-27 {
    description "initial revision.";
    reference "Based on
      3GPP TS 28.541 V15.X.XX";
  }
  typedef SliceSimultaneousUse-enum {
    type enumeration {
      enum ZERO;
      enum ONE;
      enum TWO;
      enum THREE;
      enum FOUR;
    }
  }
  typedef ServiceType-enum {
    type enumeration {
      enum eMBB;
      enum URLLC;
      enum MIoT;
      enum V2X;
    }
  }

  grouping PositioningGrp {
    description "Represents positioning support.";
    reference "Clause 3.4.20 of GSMA NG.116 ";
    
    uses ns3cmn3gpp:ServAttrComGrp ;
    leaf-list availability {
      type enumeration {
        enum CIDE_CID ;
        enum OTDOA;
        enum RF_FINGERPRINTING;
        enum AECID;
        enum HYBRID_POSITIONING;
        enum NET_RTK;
      }
      min-elements 1;
      config false;
      description "Specifies if this attribute is provided by the RAN domain 
        of the network slice and contains a list of positioning methods 
        provided by the RAN domain. If the list is empty this attribute is 
        not available in the RAN domain and the other parameters might be 
        ignored, see NG.116. Values allowed: are
        CIDE-CID (LTE and NR), OTDOA (LTE and NR), RF fingerprinting, AECID, 
        Hybrid positioning, NET-RTK.";
    }
    leaf predictionfrequency {
      type enumeration {
        enum PERSEC;
        enum PERMIN;
        enum PERHOUR;
      }
      mandatory true;
      description "Specifies how often location information is provided. 
        This parameter simply defines how often the customer is allowed to 
        request location information. This is not related to the time it 
        takes to determine the location, which is a characteristic of the 
        positioning method.
        If leaf-list availability is empty, the value has no meaning.";
        reference "NG.116";
    }
    leaf accuracy {
      type decimal64 {
         fraction-digits 2;
      } 
      units meter;
      mandatory true;
      description "Specifies the accuracy of the location information. 
        Accuracy depends on the respective positioning solution applied in the 
        RAN domain of the network slice.";
      reference "NG.116";
    }
  }

  grouping TopSliceSubnetProfileGrp {
    leaf latency {
      description "The packet transmission latency (milliseconds) through 
        the RAN, CN, and TN part of 5G network, used to evaluate 
        utilization performance of the end-to-end network slice instance.";
      reference "3GPP TS 28.554 clause 6.3.1";
      //optional support
      mandatory true;
      type uint16;
      units milliseconds;
    }
    leaf maxNumberofUEs {
      description "Specifies the maximum number of UEs may simultaneously 
        access the network slice instance.";
      //optional support
      mandatory true;
      type uint64;
    }
    list dLThptPerSliceSubnet {
      description "This attribute defines achievable data rate of the
        network slice subnet in downlink that is available ubiquitously
        across the coverage area of the slice";
      key idx;
      max-elements 1;
      leaf idx {
        description "Synthetic index for the element.";
        type uint32;
      }
      uses ns3cmn3gpp:XLThptGrp;
    }
    list dLThptPerUE {
      description "This attribute defines data rate supported by the
        network slice per UE, refer NG.116.";
      key idx;
      max-elements 1;
      leaf idx {
        description "Synthetic index for the element.";
        type uint32;
      }
      uses ns3cmn3gpp:XLThptGrp;
    }
    list uLThptPerSliceSubnet {
      description "This attribute defines achievable data rate of the
        network slice subnet in uplink that is available ubiquitously
        across the coverage area of the slice";
      key idx;
      max-elements 1;
      leaf idx {
        description "Synthetic index for the element.";
        type uint32;
      }
      uses ns3cmn3gpp:XLThptGrp;
    }
    list uLThptPerUE {
      description "This attribute defines data rate supported by the
        network slice per UE, refer NG.116";
      key idx;
      max-elements 1;
      leaf idx {
        description "Synthetic index for the element.";
        type uint32;
      }
      uses ns3cmn3gpp:XLThptGrp;
    }
    list maxPktSize {
      config false;
      key idx;
      max-elements 1;
      leaf idx {
        description "Synthetic index for the element.";
        type uint32;
      }
      description "This parameter specifies the maximum packet size 
        supported by the network slice";
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf maxSize {
        //Stage2 issue: Not defined in 28.541, guessing integer bytes
        type uint32;
        units bytes;
      }
    }
    list maxNumberofPDUSessions {
      description "Represents the maximum number of 
        concurrent PDU sessions supported by the network slice";
      config false;
      key idx;
      max-elements 1;
      leaf idx {
        description "Synthetic index for the element.";
        type uint32;
      }
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf nOofPDUSessions {
        //Stage2 issue: Not defined in 28.541, guessing integer
        type uint32;
      }
    }
    leaf sliceSimultaneousUse {
      description "This attribute describes whether a network slice
      can be simultaneously used by a device together with other 
      network slices and if so, with which other classes of network slices.";
      type SliceSimultaneousUse-enum;
    }    
    list delayTolerance {
      description "An attribute specifies the properties of service delivery 
        flexibility, especially for the vertical services that are not 
        chasing a high system performance.";
      reference "TS 22.104 clause 4.3";
      config false;
      key idx;
      max-elements 1;
      leaf idx {
        description "Synthetic index for the element.";
        type uint32;
      }
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf support {
        description "An attribute specifies whether or not the network 
          slice supports service delivery flexibility, especially for the 
          vertical services that are not chasing a high system performance.";
        type ns3cmn3gpp:Support-enum;
      }
    }
    list termDensity {
      description "An attribute specifies the overall user density over 
        the coverage area of the network slice";
      config false;
      key idx;
      max-elements 1;
      leaf idx {
        description "Synthetic index for the element.";
        type uint32;
      }
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf density {
        type uint32;
        units users/km2;
      }        
    }
    leaf activityFactor {
      //Stage2 issue: This is modeled as writable/config true in 28.542, 
      //              but that does not appear to match the description
      description "An attribute specifies the percentage value of the 
        amount of simultaneous active UEs to the total number of UEs where 
        active means the UEs are exchanging data with the network";
      reference "TS 22.261 Table 7.1-1";
      type decimal64 {
        fraction-digits 1;
      }
    }
    list coverageAreaTAList {
      description "A list of TrackingAreas where the NSI can be selected.";
      key idx; //no obvious leaf to use as a key
      leaf idx { type uint32; }
      //optional support
      min-elements 1;
      uses types3gpp:TaiGrp;
    }
    leaf uEMobilityLevel {
      description "The mobility level of UE accessing the network slice 
        instance.";
      //optional support
      type types3gpp:UeMobilityLevel;
    }
    
    leaf resourceSharingLevel {
      description "Specifies whether the resources to be allocated to the 
        network slice subnet instance may be shared with another network 
        slice subnet instance(s).";
      //optional support
      type types3gpp:ResourceSharingLevel;
    }
    leaf uESpeed {
      //Stage2 issue: This is modeled as writable/config true in 28.542, 
      //              but that does not appear to match the description
      description "An attribute specifies the maximum speed (in km/hour) 
        supported by the network slice at which a defined QoS can be 
        achieved";
      type uint32;
      units km/h;
    }
    leaf reliability {
      description "An attribute specifies in the context of network layer 
        packet transmissions, percentage value of the amount of sent 
        network layer packets successfully delivered to a given system 
        entity within the time constraint required by the targeted service, 
        divided by the total number of sent network layer packets.";
      reference "TS 22.261, TS 22.104";
      type string;
    }
    leaf serviceType {
      description "An attribute specifies the standardized network slice type. 
	  allowedValues: eMBB, URLLC, MIoT, V2X.";
      type ServiceType-enum;
    }
    list deterministicComm {
      //Stage2 issue: deterministicComm is not defined in 28.541 chapter 6, 
      //              but I guess determinComm is meant
      description "This list represents the properties of the deterministic 
        communication for periodic user traffic. Periodic traffic refers to the 
        type of traffic with periodic transmissions.";
      key idx;
      max-elements 1;
      leaf idx {
        description "Synthetic index for the element.";
        type uint32;
      }
      list servAttrCom {
        description "This list represents the common properties of service 
          requirement related attributes.";
        reference "GSMA NG.116 corresponding to Attribute categories, 
          tagging and exposure";
        config false;
        key idx;
        max-elements 1;
        leaf idx {
          description "Synthetic index for the element.";
          type uint32;
        }
        uses ns3cmn3gpp:ServAttrComGrp;
      }
      leaf availability {
        //Stage2 issue: Defined differently in 28.541 chapter 6, but XML 
        //              uses DeterminCommAvailability
        config false;
        type ns3cmn3gpp:DeterminCommAvailability;
      }
      leaf periodicityList {
        //Stage2 issue: Not defined in 28.541 chapter 6. XML and YAML 
        //              says "string".
        type string;
      }
    }
    leaf survivalTime {
      description "An attribute specifies the time that an application 
        consuming a communication service may continue without an 
        anticipated message.";
      reference "TS 22.104 clause 5";
      type string;
    }
    list positioning {
      key predictionfrequency;
      min-elements 1;
      max-elements 1;
      description "Specifies whether the network slice provides 
        geo-localization methods or supporting methods";
      reference "Clause 3.4.20 of NG.116";
      uses PositioningGrp;
    }
  }
    
  grouping CNSliceSubnetProfileGrp {
    leaf latency {
      description "The packet transmission latency (milliseconds) through 
        the RAN, CN, and TN part of 5G network, used to evaluate 
        utilization performance of the end-to-end network slice instance.";
      reference "3GPP TS 28.554 clause 6.3.1";
      //optional support
      mandatory true;
      type uint16;
      units milliseconds;
    }
    leaf maxNumberofUEs {
      description "Specifies the maximum number of UEs may simultaneously 
        access the network slice instance.";
      //optional support
      mandatory true;
      type uint64;
    }
    list dLThptPerSliceSubnet {
      description "This attribute defines achievable data rate of the
        network slice subnet in downlink that is available ubiquitously
        across the coverage area of the slice";
      key idx;
      max-elements 1;
      leaf idx {
        description "Synthetic index for the element.";
        type uint32;
      }
      uses ns3cmn3gpp:XLThptGrp;
    }
    list dLThptPerUE {
      description "This attribute defines data rate supported by the
        network slice per UE, refer NG.116.";
      key idx;
      max-elements 1;
      leaf idx {
        description "Synthetic index for the element.";
        type uint32;
      }
      uses ns3cmn3gpp:XLThptGrp;
    }
    list uLThptPerSliceSubnet {
      description "This attribute defines achievable data rate of the
        network slice subnet in uplink that is available ubiquitously
        across the coverage area of the slice";
      key idx;
      max-elements 1;
      leaf idx {
        description "Synthetic index for the element.";
        type uint32;
      }
      uses ns3cmn3gpp:XLThptGrp;
    }
    list uLThptPerUE {
      description "This attribute defines data rate supported by the
        network slice per UE, refer NG.116";
      key idx;
      max-elements 1;
      leaf idx {
        description "Synthetic index for the element.";
        type uint32;
      }
      uses ns3cmn3gpp:XLThptGrp;
    }
    list maxPktSize {
      config false;
      key idx;
      max-elements 1;
      leaf idx {
        description "Synthetic index for the element.";
        type uint32;
      }
      description "This parameter specifies the maximum packet size 
        supported by the network slice";
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf maxSize {
        //Stage2 issue: Not defined in 28.541, guessing integer bytes
        type uint32;
        units bytes;
      }
    }
    list maxNumberofPDUSessions {
      description "Represents the maximum number of 
        concurrent PDU sessions supported by the network slice";
      config false;
      key idx;
      max-elements 1;
      leaf idx {
        description "Synthetic index for the element.";
        type uint32;
      }
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf nOofPDUSessions {
        //Stage2 issue: Not defined in 28.541, guessing integer
        type uint32;
      }
    }
    leaf sliceSimultaneousUse {
      description "This attribute describes whether a network slice
      can be simultaneously used by a device together with other 
      network slices and if so, with which other classes of network slices.";
      type SliceSimultaneousUse-enum;
    }  
    list delayTolerance {
      description "An attribute specifies the properties of service delivery 
        flexibility, especially for the vertical services that are not 
        chasing a high system performance.";
      reference "TS 22.104 clause 4.3";
      config false;
      key idx;
      max-elements 1;
      leaf idx {
        description "Synthetic index for the element.";
        type uint32;
      }
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf support {
        description "An attribute specifies whether or not the network 
          slice supports service delivery flexibility, especially for the 
          vertical services that are not chasing a high system performance.";
        type ns3cmn3gpp:Support-enum;
      }
    }
    list coverageAreaTAList {
      description "A list of TrackingAreas where the NSI can be selected.";
      key idx; //no obvious leaf to use as a key
      leaf idx { type uint32; }
      //optional support
      min-elements 1;
      uses types3gpp:TaiGrp;
    }
    leaf resourceSharingLevel {
      description "Specifies whether the resources to be allocated to the 
        network slice subnet instance may be shared with another network 
        slice subnet instance(s).";
      //optional support
      type types3gpp:ResourceSharingLevel;
    }

    list deterministicComm {
      //Stage2 issue: deterministicComm is not defined in 28.541 chapter 6, 
      //              but I guess determinComm is meant
      description "This list represents the properties of the deterministic 
        communication for periodic user traffic. Periodic traffic refers to the 
        type of traffic with periodic transmissions.";
      key idx;
      max-elements 1;
      leaf idx {
        description "Synthetic index for the element.";
        type uint32;
      }
      list servAttrCom {
        description "This list represents the common properties of service 
          requirement related attributes.";
        reference "GSMA NG.116 corresponding to Attribute categories, 
          tagging and exposure";
        config false;
        key idx;
        max-elements 1;
        leaf idx {
          description "Synthetic index for the element.";
          type uint32;
        }
        uses ns3cmn3gpp:ServAttrComGrp;
      }
      leaf availability {
        //Stage2 issue: Defined differently in 28.541 chapter 6, but XML 
        //              uses DeterminCommAvailability
        config false;
        type ns3cmn3gpp:DeterminCommAvailability;
      }
      leaf periodicityList {
        //Stage2 issue: Not defined in 28.541 chapter 6. XML and YAML 
        //              says "string".
        type string;
      }
    }
  }

  grouping PositioningRANSubnetGrp {
    description "Represents positioning support in RAN domain";
    leaf-list availability {
      type enumeration {
        enum CIDE_CID ;
        enum OTDOA;
        enum RF_FINGERPRINTING;
        enum AECID;
        enum HYBRID_POSITIONING;
        enum NET_RTK;
      }
      config false;
      description "Specifies if this attribute is provided by the RAN domain 
        of the network slice and contains a list of positioning methods 
        provided by the RAN domain. If the list is empty this attribute is 
        not available in the RAN domain and the other parameters might be 
        ignored, see NG.116. Values allowed: are
        CIDE-CID (LTE and NR), OTDOA (LTE and NR), RF fingerprinting, AECID, 
        Hybrid positioning, NET-RTK.";
    }
    leaf predictionfrequency {
      type enumeration {
        enum PERSEC;
        enum PERMIN;
        enum PERHOUR;
      }
      mandatory true;
      description "Specifies how often location information is provided. 
        This parameter simply defines how often the customer is allowed to 
        request location information. This is not related to the time it 
        takes to determine the location, which is a characteristic of the 
        positioning method.
        If leaf-list availability is empty, the value has no meaning.";
        reference "NG.116";
    }
    leaf accuracy {
      type decimal64 {
         fraction-digits 2;
      } 
      units meter;
      mandatory true;
      description "Specifies the accuracy of the location information. 
        Accuracy depends on the respective positioning solution applied in the 
        RAN domain of the network slice.";
      reference "NG.116";
    }
  }
  
  grouping RANSliceSubnetProfileGrp {
    description "Represents the RANSliceSubnetProfile datatype";
    leaf latency {
      description "The packet transmission latency (milliseconds) through 
        the RAN, CN, and TN part of 5G network, used to evaluate 
        utilization performance of the end-to-end network slice instance.";
      reference "3GPP TS 28.554 clause 6.3.1";
      //optional support
      mandatory true;
      type uint16;
      units milliseconds;
    }
    leaf maxNumberofUEs {
      description "Specifies the maximum number of UEs may simultaneously 
        access the network slice instance.";
      //optional support
      mandatory true;
      type uint64;
    }
    list dLThptPerSliceSubnet {
      description "This attribute defines achievable data rate of the
        network slice subnet in downlink that is available ubiquitously
        across the coverage area of the slice";
      key idx;
      max-elements 1;
      leaf idx {
        description "Synthetic index for the element.";
        type uint32;
      }
      uses ns3cmn3gpp:XLThptGrp;
	  }	
    list dLThptPerUE {
      description "This attribute defines data rate supported by the
        network slice per UE, refer NG.116.";
      key idx;
      max-elements 1;
      leaf idx {
        description "Synthetic index for the element.";
        type uint32;
      }
      uses ns3cmn3gpp:XLThptGrp;
    }
    list uLThptPerSliceSubnet {
      description "This attribute defines achievable data rate of the
        network slice subnet in uplink that is available ubiquitously
        across the coverage area of the slice";
      key idx;
      max-elements 1;
      leaf idx {
        description "Synthetic index for the element.";
        type uint32;
      }
      uses ns3cmn3gpp:XLThptGrp;
    }
    list uLThptPerUE {
      description "This attribute defines data rate supported by the
        network slice per UE, refer NG.116";
      key idx;
      max-elements 1;
      leaf idx {
        description "Synthetic index for the element.";
        type uint32;
      }
      uses ns3cmn3gpp:XLThptGrp;
    }
    list maxPktSize {
      config false;
      key idx;
      max-elements 1;
      leaf idx {
        description "Synthetic index for the element.";
        type uint32;
      }
      description "This parameter specifies the maximum packet size 
        supported by the network slice";
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf maxSize {
        //Stage2 issue: Not defined in 28.541, guessing integer bytes
        type uint32;
        units bytes;
      }
    }
    list delayTolerance {
      description "An attribute specifies the properties of service delivery 
        flexibility, especially for the vertical services that are not 
        chasing a high system performance.";
      reference "TS 22.104 clause 4.3";
      config false;
      key idx;
      max-elements 1;
      leaf idx {
        description "Synthetic index for the element.";
        type uint32;
      }
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf support {
        description "An attribute specifies whether or not the network 
          slice supports service delivery flexibility, especially for the 
          vertical services that are not chasing a high system performance.";
        type ns3cmn3gpp:Support-enum;
      }
    }
    leaf sliceSimultaneousUse {
      description "This attribute describes whether a network slice
      can be simultaneously used by a device together with other 
      network slices and if so, with which other classes of network slices.";
      type SliceSimultaneousUse-enum;
    }  
    list termDensity {
      description "An attribute specifies the overall user density over 
        the coverage area of the network slice";
      config false;
      key idx;
      max-elements 1;
      leaf idx {
        description "Synthetic index for the element.";
        type uint32;
      }
      list servAttrCom {
        description "This list represents the common properties of service 
          requirement related attributes.";
        reference "GSMA NG.116 corresponding to Attribute categories, 
          tagging and exposure";
        key idx;
        max-elements 1;
        leaf idx {
          description "Synthetic index for the element.";
          type uint32;
        }
        uses ns3cmn3gpp:ServAttrComGrp;
      }
      leaf density {
        type uint32;
        units users/km2;
      }        
    }
    leaf activityFactor {
      //Stage2 issue: This is modeled as writable/config true in 28.542, 
      //              but that does not appear to match the description
      description "An attribute specifies the percentage value of the 
        amount of simultaneous active UEs to the total number of UEs where 
        active means the UEs are exchanging data with the network";
      reference "TS 22.261 Table 7.1-1";
      type decimal64 {
        fraction-digits 1;
      }
    }
    list coverageAreaTAList {
      description "A list of TrackingAreas where the NSI can be selected.";
      key idx; //no obvious leaf to use as a key
      leaf idx { type uint32; }
      //optional support
      min-elements 1;
      uses types3gpp:TaiGrp;
    }
    leaf uEMobilityLevel {
      description "The mobility level of UE accessing the network slice 
        instance.";
      //optional support
      type types3gpp:UeMobilityLevel;
    }
    
    leaf resourceSharingLevel {
      description "Specifies whether the resources to be allocated to the 
        network slice subnet instance may be shared with another network 
        slice subnet instance(s).";
      //optional support
      type types3gpp:ResourceSharingLevel;
    }
    leaf uESpeed {
      //Stage2 issue: This is modeled as writable/config true in 28.542, 
      //              but that does not appear to match the description
      description "An attribute specifies the maximum speed (in km/hour) 
        supported by the network slice at which a defined QoS can be 
        achieved";
      type uint32;
      units km/h;
    }
    leaf reliability {
      description "An attribute specifies in the context of network layer 
        packet transmissions, percentage value of the amount of sent 
        network layer packets successfully delivered to a given system 
        entity within the time constraint required by the targeted service, 
        divided by the total number of sent network layer packets.";
      reference "TS 22.261, TS 22.104";
      type string;
    }
    leaf serviceType {
      description "An attribute specifies the standardized network slice type. 
	  allowedValues: eMBB, URLLC, MIoT, V2X.";
      type ServiceType-enum;
    }
    list deterministicComm {
      //Stage2 issue: deterministicComm is not defined in 28.541 chapter 6, 
      //              but I guess determinComm is meant
      description "This list represents the properties of the deterministic 
        communication for periodic user traffic. Periodic traffic refers to the 
        type of traffic with periodic transmissions.";
      key idx;
      max-elements 1;
      leaf idx {
        description "Synthetic index for the element.";
        type uint32;
      }
      list servAttrCom {
        description "This list represents the common properties of service 
          requirement related attributes.";
        reference "GSMA NG.116 corresponding to Attribute categories, 
          tagging and exposure";
        config false;
        key idx;
        max-elements 1;
        leaf idx {
          description "Synthetic index for the element.";
          type uint32;
        }
        uses ns3cmn3gpp:ServAttrComGrp;
      }
      leaf availability {
        //Stage2 issue: Defined differently in 28.541 chapter 6, but XML 
        //              uses DeterminCommAvailability
        config false;
        type ns3cmn3gpp:DeterminCommAvailability;
      }
      leaf periodicityList {
        //Stage2 issue: Not defined in 28.541 chapter 6. XML and YAML 
        //              says "string".
        type string;
      }
    }
    leaf survivalTime {
      description "An attribute specifies the time that an application 
        consuming a communication service may continue without an 
        anticipated message.";
      reference "TS 22.104 clause 5";
      type string;
    }
    list positioning {
      min-elements 1;
      max-elements 1;
      description "Specifies whether the RAN domain of the network slice 
        provides geo-localization methods or supporting methods.";
      reference "Clause 3.4.20 of NG.116 [50].";
      uses PositioningRANSubnetGrp;
    }
  }

  grouping SliceProfileGrp {
    leaf sliceProfileId {
      description "A unique identifier of the property of network slice 
        subnet related requirement should be supported by the network 
        slice subnet instance.";
      type types3gpp:DistinguishedName;
    }
    
    list sNSSAIList {
      description "List of S-NSSAIs the managed object is capable of 
        supporting. (Single Network Slice Selection Assistance Information)
        An S-NSSAI has an SST (Slice/Service type) and an optional SD
        (Slice Differentiator) field.";
      key idx;
      unique "sst sd";
      leaf idx {
        description "Synthetic index for the element.";
        type uint32;
      }
      uses types5g3gpp:SNssai;
    }
    
    list pLMNIdList {
      description "List of at most six entries of PLMN Identifiers, but at 
        least one (the primary PLMN Id).  The PLMN Identifier is composed 
        of a Mobile Country Code (MCC) and a Mobile Network Code (MNC).";
      min-elements 1;
      max-elements 6;
      key "mcc mnc";
      ordered-by user;
      uses types3gpp:PLMNId;
    }
    
    leaf maxNumberofUEs {
      description "Specifies the maximum number of UEs may simultaneously 
        access the network slice instance.";
      //optional support
      mandatory true;
      type uint64;
    }
    
    list coverageAreaTAList {
      description "A list of TrackingAreas where the NSI can be selected.";
      key idx; //no obvious leaf to use as a key
      leaf idx { type uint32; }
      //optional support
      min-elements 1;
      uses types3gpp:TaiGrp;
    }
    
    leaf latency {
      description "The packet transmission latency (milliseconds) through 
        the RAN, CN, and TN part of 5G network, used to evaluate 
        utilization performance of the end-to-end network slice instance.";
      reference "3GPP TS 28.554 clause 6.3.1";
      //optional support
      mandatory true;
      type uint16;
      units milliseconds;
    }
    
    leaf uEMobilityLevel {
      description "The mobility level of UE accessing the network slice 
        instance.";
      //optional support
      type types3gpp:UeMobilityLevel;
    }
    
    leaf resourceSharingLevel {
      description "Specifies whether the resources to be allocated to the 
        network slice subnet  instance may be shared with another network 
        slice subnet instance(s).";
      //optional support
      type types3gpp:ResourceSharingLevel;
    }
    list CNSliceSubnetProfile {
      description " This represents the requirements for the top slice associated with the 
	  network slice. ";
      key idx;
      max-elements 1;
      leaf idx {
        description "Synthetic index for the element.";
        type uint32;
      }
	  uses TopSliceSubnetProfileGrp;
    }
    list RANSliceSubnetProfile {
      description " This represents the requirements for the top slice associated with the 
	  network slice. ";
      key idx;
      max-elements 1;
      leaf idx {
        description "Synthetic index for the element.";
        type uint32;
      }
	  uses TopSliceSubnetProfileGrp;
    }
    list TopSliceSubnetProfile {
      description " This represents the requirements for the top slice associated with the 
	  network slice. ";
      key idx;
      max-elements 1;
      leaf idx {
        description "Synthetic index for the element.";
        type uint32;
      }
	  uses TopSliceSubnetProfileGrp;
    }
  }
}

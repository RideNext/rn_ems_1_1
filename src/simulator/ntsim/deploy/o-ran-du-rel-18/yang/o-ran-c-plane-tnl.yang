module o-ran-c-plane-tnl{
  yang-version 1.1;
  namespace "urn:o-ran:c-plane-tnl:1.0";
  prefix "o-ran-c-tnl";
  
  organization 
  "O-RAN Alliance";

contact
  "www.o-ran.org";

description 
  "This module defines the YANG definitions for Transport Network Layer (TNL)
   configuration for C-plane end-points at O-DU and O-CU. This module is to be 
   used to augment 3GPP SA5 data models.

   Copyright 2020 the O-RAN Alliance.

   THIS SOFTWARE IS PROVIDED BY THE COPYRIGHT HOLDERS AND CONTRIBUTORS 'AS IS'
   AND ANY EXPRESS OR IMPLIED WARRANTIES, INCLUDING, BUT NOT LIMITED TO, THE
   IMPLIED WARRANTIES OF MERCHANTABILITY AND FITNESS FOR A PARTICULAR PURPOSE
   ARE DISCLAIMED. IN NO EVENT SHALL THE COPYRIGHT HOLDER OR CONTRIBUTORS BE
   LIABLE FOR ANY DIRECT, INDIRECT, INCIDENTAL, SPECIAL, EXEMPLARY, OR
   CONSEQUENTIAL DAMAGES (INCLUDING, BUT NOT LIMITED TO, PROCUREMENT OF
   SUBSTITUTE GOODS OR SERVICES; LOSS OF USE, DATA, OR PROFITS; OR BUSINESS
   INTERRUPTION) HOWEVER CAUSED AND ON ANY THEORY OF LIABILITY, WHETHER IN
   CONTRACT, STRICT LIABILITY, OR TORT (INCLUDING NEGLIGENCE OR OTHERWISE)
   ARISING IN ANY WAY OUT OF THE USE OF THIS SOFTWARE, EVEN IF ADVISED OF THE
   POSSIBILITY OF SUCH DAMAGE.

   Redistribution and use in source and binary forms, with or without
   modification, are permitted provided that the following conditions are met:

   * Redistributions of source code must retain the above copyright notice,
     this list of conditions and the above disclaimer.
   * Redistributions in binary form must reproduce the above copyright notice,
     this list of conditions and the above disclaimer in the documentation
     and/or other materials provided with the distribution.
   * Neither the Members of the o-RAN Alliance nor the names of its
     contributors may be used to endorse or promote products derived from
     this software without specific prior written permission.";

  revision "2020-09-25" {
    description
      "version 1.0.0 - first release of O-RAN O1 for O-DU YANG models";

    reference "ORAN-WG5.MP.0-v01.00";
  }
  
  typedef dscp-marking-value {
    type uint8 {
      range "0..63";
    }
    description "type definition for DSCP marking";
  }
  
  grouping dscp-marking {
    leaf c-plane-dscp {
      type dscp-marking-value;
      mandatory true;
      description "dscp-marking for F1-C, X2-C, Xn-C, NG-C or E1 traffic";
    }     
    description "grouping of DSCP marking";
  }

  
  grouping sctp-configuration {
    container sctp-configuration {
      leaf association-hbt-interval {
        type uint8 {
          range "0..60";
        }
        default 30;
        description "SCTP association heart-beat interval";
      }
      leaf max-burst {
        type uint8 {
          range "2..8";
        }
        default 4;
        description "SCTP max burst";
      }
      leaf association-max-retries {
        type uint8 {
          range "1..30";          
        }
        default 10;
        description "SCTP association max retries";
      }
      leaf rto-initial {
        type uint16 {
          range "10..60000";          
        }
        default 3000;
        description "SCTP RTO expiry timer initial value";
      }
      leaf rto-max {
        type uint16 {
          range "10..60000";          
        }
        default 60000;
        description "SCTP RTO expiry timer max value";
      }        
      leaf rto-min {
        type uint16 {
          range "10..60000";          
        }
        default 1000;
        description "SCTP RTO expiry timer min value";
      } 
      leaf ack-delay {
        type uint16 {
          range "20..500";          
        }
        default 200;
        description "SCTP ACK delay time";
      }        
      leaf ack-frequency {
        type uint8 {
          range "1..25";          
        }
        default 5;
        description "SCTP ACK frequency";
      }    
      leaf cookie-life {
        type uint16 {
          range "1..60000";          
        }
        default 60;
        description "SCTP cookie life value";
      }       
      leaf path-max-retransmits {
        type uint8 {
          range "1..30";          
        }
        default 5;
        description "SCTP path max retransmits value";
      }    
      leaf max-init-retransmits {
        type uint8 {
          range "1..30";          
        }
        default 8;
        description "SCTP max INIT retransmits";
      }         
      description "container for SCTP configuration"; 
    }
    description "grouping SCTP configurations";    
  }  
}
